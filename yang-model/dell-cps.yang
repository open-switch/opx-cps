module dell-base-cps {
    namespace "http://www.dell.com/esg/networking/os10/dell-cps";
  prefix "cps";

  typedef config-type {
  
    description "This enum range is designed to help with the configuration of objects in the system.  A application can set the following enums
  on any objects that they perform a commit operation on (set/delete/create).
 
  Using this information (configuration type), an application can make changes to:
  1) Running configuration - used for warm restart or application/process restart
  2) Startup configuration - used in the case that the system goes through a full cold start process
  3) Running configuration only - used in the case that an application is dynamically changing the system based on observations or
          other actions that should not be stored for cold starts (eg.. iscsi auto provisioning, temporary IP address, etc..)";
          
    type enumeration {
      enum "startup-config" {
        value 1;
        description
          "This configuration should be placed into the startup config only and has no effect on the existing running config.";
      }
      enum "running-config" {
        value 2;
        description
          "This configuration should be placed into the running configuration but is a candidate in the future for copying to startup
          based on user requests.";
      }
      enum "startup-and-running" {
        value 3;
        description
          "This configuration request should be placed in the running config and startup config both";
      }
      enum "running-config-only" {
        value 4;
        description "This configuration request should never be copied into the startup configuration.  This is appliciable for running
            configuration only.";
      }
    }
  }

  typedef group_type {
    description "Type of supported DB clusters";
    type enumeration {
      enum NODAL {
        value 1;
        description "Data resides on each node and is not duplicated by node group";
      }
      enum GLOBAL {
        value 2;
        description "Data is stored in a global database and replicated to a backup node";
      }
    }
  }


  list node-details {
    description "This object contains a list of aliases for a node.  Any one of the aliases will be converted
              into the name.

              For instance lets asume that there was a node with an IP address of 10.11.11.11 and
              there was a port 443 that contained a service. The name would be 10.11.11.11:443 while on that node,
              lets say we wanted a user friendly name and therefore called the entity joe or jane but when you see
              joe or jain, you want to convert these aliases for the node back to 10.11.11.11:443.";
    key "name";
    leaf name {

      description "The name to use as a replacement for any of the alias attributes.";
      type string;
    }
    leaf-list alias {
      description "A list of alias that can be convered back to the name.";
      type string;
    }
  }

  list node-group {
    description "This object is used to describe the mapping of a group ID to a list of node IP/port combinations.";
    key "name";

    leaf name {
      description "The name of the group.";
      type string;
    }
    list node {
      leaf name {
        description "The name of the node entry. (an alias for the ip)";
        type string;
      }
      leaf ip {
        description "The IP address and port of the element.  Valid IP address/port
                    combinations are IPv4:port or [IPv6]:port";
        type string;
      }
    }
    leaf type {
      description "Type of the group cluster";
      type group_type;
    }
  }

  list connectivity-group {
    description "This object is used to describe the mapping of a group ID to a list of node IP/port combinations.";
    key "name";

    leaf name {
      description "The name of the group.";
      type string;
    }
    leaf timestamp {
      description "Timestamp when the group was created";
      type string;
    }
    list node {
      leaf name {
        description "The name of the node entry. (an alias for the ip)";
        type string;
      }
      leaf ip {
        description "The IP address and port of the element.  Valid IP address/port
                    combinations are IPv4:port or [IPv6]:port";
        type string;
      }
      leaf tunnel-ip {
        description "The IP addres and port of the stunnel client. Valid IP address/port
                    combinations are IPv4:port or [IPv6]:port";
        type string;
      }
      leaf timestamp {
        description "Timestamp when the node has connectivity established";
        type string;
      }

    }
    leaf type {
      type uint32;
      description "Type of the group cluster";
      type group_type;
    }
  }

  container object-group {
    description "These attributes are placed in objects by CPS infrastructure and provide additional information or change
                behaviour as needed.";
    leaf group {
      description "This attribute holds the group ID if specified.";
      type string;
    }
    leaf node {
      description "This attribute contains the node id.";
      type string;
    }
    leaf transaction {
      description "In the case of commit operations (and the object is cacheable and doesn't exist at the time
              due to a restart, then an Inprogress return code will be provided and this transaction ID
              can be used to monitor the state of the transaction.";
      type uint64;
    }
    leaf failed-nodes {
      description "This attribute is used in an object to indicate which nodes did not process the request due to
              connectivity reasons. Nodes are in a single string separated by comma (,).";
      type string;
    }
    leaf wildcard-search {
        description "This attribute is true if the attributes in the object (primarily used for get requests) contain wildcard characters.
        For instance if someone was searching for a python interface/vlan object with all names starting with eth, the python dictionary
        would appear as follows:
            {
                'key': 'interface/vlan',
                'data' : { 'interface/vlan/name' : 'eth*',
                           'cps/object-group/wildcard-search': True }
            }
        ";
        type boolean;
    }

    leaf exact-match {
      description "If this attribute is present in an filter object, then the attributes in the object will be used to find
          objects who's attributes match the attribute values specified in this filter object.
          For examplpe:
            A { 1=A,2=B } will match B { 1=A,2=B,C=3,D=4 }
            A { 1=A,2=B } will not match { 1=A,C=3 }
            ";
      type boolean;
    }
    leaf return-code {
      description "In the event that an API needs to store a return code within an object itself, they can use this field.  This field is
                  left as an int size.";
      type uint32;
    }
    leaf return-string {
      description "This field can be used to store a string description (tag) of either an error that occurued during the requested operation or additional
            information to the successful request (less likely).";
      type string;
    }
    leaf get-next {
        description "If this attribute is present in an object, then the caller would like the next object in lexicographic order";
        type boolean;
    }
    leaf number-of-entries {
        description "Provide the number of entries to retrieve at one time to support the concept of range along with the get next attribute";
      type uint64;
    }    
    leaf config-type {
    	description "This attribute indicates the storage options for the object if supported.  This storage type can be
    		1) Store to running
    		2) Store to statup 
    		3) Store to both running and startup";
      type config-type;
    }
    leaf continue-on-failure {
    	description "This attribute if provided will control the behaviour of CPS in error conditions for 
    		both the gets and commits.
    		In the case of a commit, if this attribute is present and false, then a rollback will not be performed 
    		and the operation will continue.  Errors discovered will be returned within the objects themselves.
    		
    		In the case of a get, if this attribute is present on the filter, all errors in gets will be ignored as well
    		and in this case, objects will not be returned.
    		
    		Eg..1 commit transaction with 3 objects and one object fails (with this flag set to false) the CPS layer 
    		will continue to perform all three commits and will not rollback.
    		
    		Eg..1 in the get case, with 3 object filters, if there is no results or a failure in the backend component,
    		CPS will ignore the error and continue.";
    	default false;  
    	type boolean;
    }
    leaf sequence {
    	description "This field will hold a CPS internal sequence number.  This 
    		number will be used to determine if duplicate events are being sent and
    		to help track out of order events.";
    	type uint64;
    }
    leaf thread-id {
    	description "The thread ID of the person making the request or sending the event.
    	This is used internally for debugging purposes only.";
    	type uint64;
    }
    leaf timestamp {
    	description "This is the timestamp of when the event is generated.";
    	type uint64;
    }
    
    leaf user-timestamp-nsec {
        description "This is a user-defined timestamp in nano-seconds that can be inserted into an object.";
        type uint64;
    }
  }

  list connection-entry {
    key "name";
    leaf name {
      type string;
    }
    leaf ip {
      type string;
    }
    leaf group {
      type string;
    }
    leaf connection-state {
      type boolean;
    }
  }

  list db-instance{
    key "group node-id";
    leaf group{
        type string;
        description "Group name";
    }

    leaf node-id{
        type string;
        description "Node name";
    }

    leaf port{
        type string;
        description "System port where DB Instance was started for given group";
    }
  }

  list connection-object{
    key "name";
    leaf name{
        type string;
        description "Node name";
    }

    leaf addr{
        type string;
        description "The IP address and port of the element.  Valid IP address/port
                    combinations are IPv4:port or [IPv6]:port";
    }

    leaf tunnel{
        type string;
        config false;
        description "System port where tunneling from DB to other node occurs";
    }
    leaf timestamp {
        type string;
        description "Timestamp when the node has connectivity established";
      }
  }

  list service-instance {
    description "This service is registered by the CPS infra and can be used to provide details about active registrations in the system.";
    config false;
    key "name";
    
    leaf name {
        type string;
        description "The service name or some type of string representation of the service instance.";
    }
    leaf connection-information {
        type string;
        description "Protocol specific connection information.  For instance, in the case of a UNIX domain socket connection this is the socket name.";        
    }
    leaf-list registered-key {
        type string;
        description "The registered keys that are associated with the service.";        
    }
        
  }  
}
